module update-a {
  yang-version 1.1;
  namespace "http://example.com/update-a";
  prefix udp-a;
  
  revision 2026-02-15;
  revision 2026-02-10; 

  identity table-type;
  identity basic-table {
    base table-type;
  }

  container table {
    leaf surface {
      type uint32;
    }

    leaf height {
      type uint32;
    }
  }

  container chair {
    leaf height {
      type uint32;
    }
  }
}
